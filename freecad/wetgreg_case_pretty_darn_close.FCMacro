"""
WetGregCase — Parametric PartDesign Enclosure for the Dilder PCB
===============================================================
Proper PartDesign model (like dilder_rev2_mk2): every part is a Body built
from a constrained sketch + Pad / Pocket / Fillet / Thickness / primitive
chain, with ALL key dimensions driven by the "Parameters" spreadsheet.

  * Edit any cell in the Parameters sheet and press Ctrl+Shift+R to recompute.
  * Add or adjust fillets/chamfers directly on the feature tree in the GUI.
  * Clean B-rep solids (no fused-primitive overlaps) -> slice cleanly for print.

Bodies:
  BackPlate   — board carrier: wraps the board edge, PCB rests on a shelf,
                closed back panel (clears the Pico), curved back edge.
  FrontCover  — screen lid: constant-wall curved shell, screen window sized
                inside the screw holes, round joystick boss, lap tongue.
  Thumbpiece  — snap cap over the 5-way joystick.
  Dilder_Assembly — imported KiCad STEP (reference; headers stripped, screen
                aligned to the front face).

Frame: local = (KiCad_X - 46.70, KiCad_StepY + 88.0, Z); Z=0 = PCB bottom.

Run:  FreeCAD > Macro > Run, or `freecadcmd wetgreg_case.FCMacro`
"""

import math, os
import FreeCAD as App
import Part
import Sketcher

V = App.Vector
ROT0 = App.Rotation()
GUI = App.GuiUp
DOC = "WetGregCase"

# =====================================================================
# PARAMETERS  (alias, value, description)  -> Parameters spreadsheet
# =====================================================================
PARAMS = [
    # --- Board (from KiCad) ---
    ("board_w",   96.80, "Board width X (1 mm shorter than the KiCad nominal)"),
    ("board_h",   42.012,"Board height Y"),
    ("board_t",    1.60, "PCB thickness"),
    ("board_r",    5.00, "Board corner radius"),
    # --- Fit / walls ---
    ("clear",      0.30, "PCB-to-wall clearance per side"),
    ("wall",       2.00, "Wall thickness"),
    ("ext_xmin",   1.20, "Case extension on -X (just past the screen edge; front = lip + PCB)"),
    ("corner_r",   7.30, "Outer corner radius (board_r+clear+wall)"),
    # --- Screen side (-Z, front lid) ---
    ("screen_top", 12.40,"Front-cover depth (screen standoff + 1mm)"),
    ("front_curve",6.00, "Aggressive front-edge curve radius"),
    # --- Seam / backplate (deep cover that clips onto the front lid) ---
    ("ftop",       0.00, "Front-plate top / seam Z (= PCB rest / mating face)"),
    ("back_above", 8.50, "Backplate depth above the seam (houses USB-C + Pico; +1 to clear the Pico micro-USB)"),
    ("back_curve", 6.00, "Back-edge curve radius (matches the front)"),
    # --- PCB ledge inside the FRONT plate (walls come in to support the board) ---
    ("ledge_in",   2.00, "Ledge reach in from the wall (board rests on it)"),
    ("ledge_th",   1.20, "Ledge thickness"),
    ("ledge_depth",10.40,"Ledge rib depth = screen_top-wall: runs down to the front floor, merging with the curved wall"),
    ("shelf_w",    1.60, "(legacy) board-edge reach"),
    # --- Battery connector gap (CN1 on the screen side) ---
    ("bat_cx",    41.50, "Battery connector CN1 centre X"),
    ("bat_cy",     2.50, "Battery connector CN1 centre Y"),
    ("bat_gap_w", 13.00, "Battery connector / cable gap width"),
    ("bat_gap_d",  7.00, "Battery gap depth into the board (stays below the window)"),
    ("bat_floor",  2.40, "Solid front skin left under the battery gap (>= wall, keeps the front floor whole + printable)"),
    # --- Flush lap joint + discrete snap-fit (inside the lap; no added thickness) ---
    ("lap",        3.00, "Lap tongue height (engagement; lives inside the backplate)"),
    ("tongue_t",   1.00, "Tongue thickness (thin -> flexes to snap)"),
    ("lap_fit",    0.20, "Tongue-to-relief slip gap"),
    ("bead_proj",  0.40, "Snap bead projection past the tongue (interference = proj-lap_fit)"),
    ("bead_h",     1.20, "Snap bead height (Z)"),
    ("bead_lead",  0.80, "Snap bead lead-in (top chamfer for assembly)"),
    ("snap_w",     6.00, "Snap bead width along the wall"),
    # --- Screen window (sized inside the 4 M2 screw holes) ---
    ("win_x0",    12.60, "Window X min (long edge shaved 2mm)"),
    ("win_x1",    63.60, "Window X max (long edge shaved 2mm; long edges 4mm shorter)"),
    ("win_y0",     7.10, "Window Y min (1mm shy of screen PCB)"),
    ("win_y1",    35.10, "Window Y max (1mm shy of screen PCB)"),
    # --- USB-C opening (+X) ---
    ("usb_cy",    21.00, "USB-C centre Y"),
    ("usb_w",      9.70, "USB-C opening width Y"),
    ("usb_z0",     0.00, "USB-C opening Z bottom (= lip top)"),
    ("usb_z1",     5.00, "USB-C opening Z top"),
    ("usb_r",      1.00, "USB-C opening corner radius"),
    # --- Power-switch slot (-Y) ---
    ("sw_x0",     47.50, "Switch slot X min"),
    ("sw_x1",     53.50, "Switch slot X max"),
    ("sw_z0",      1.00, "Switch slot Z bottom"),
    ("sw_z1",      3.30, "Switch slot Z top"),
    # --- Joystick / boss / thumbpiece ---
    ("joy_cx",    81.55, "Joystick centre X"),
    ("joy_cy",    21.30, "Joystick centre Y"),
    ("joy_hole_d",12.00, "Joystick hole diameter"),
    ("joy_boss_d",20.00, "Joystick boss outer diameter"),
    ("joy_pad_th", 5.00, "Joystick boss thickness (solar-connector room)"),
    ("thumb_od",  11.00, "Thumb cap outer diameter"),
    ("thumb_h",    4.50, "Thumb cap height"),
    ("thumb_dish_r",12.00,"Thumb dish sphere radius"),
    ("thumb_dish_d",0.60,"Thumb dish depth"),
    ("thumb_sock", 3.30, "Thumb socket (square)"),
    ("thumb_sock_d",3.50,"Thumb socket depth"),
    # --- snap-bead positions (fraction along each wall) ---
    ("snap_n_long", 2, "Snap beads per long wall"),
]
PV = {a: v for (a, v, _) in PARAMS}

def SP(alias):
    return f"Parameters.{alias}"

# Derived (literal positions; sizes/heights also live-bound below) ----
BW, BH, BT, BR = PV["board_w"], PV["board_h"], PV["board_t"], PV["board_r"]
C, W, EXT = PV["clear"], PV["wall"], PV["ext_xmin"]
front_outer_z = -PV["screen_top"]                 # -11.4
front_floor_inner = front_outer_z + PV["wall"]    # -9.4 (front floor inner face)
seam_z        =  PV["ftop"]                        # 5.5  (front-plate top / clip seam, above the Pico)
base_top_z    =  seam_z + PV["back_above"]         # 7.5  (backplate cap top)
pcb_rest_z    =  0.0                               # board bottom rests on the front-plate ledge
EINK_HOLES = [(2.4, 9.0), (2.4, 33.4), (68.8, 9.0), (68.8, 33.4)]   # M2 mount holes (local)
# outer footprint
OX0, OY0 = -(EXT + C + W), -(C + W)
OX1, OY1 =  BW + C + W,     BH + C + W
# inner cavity (board + clear, extended -X)
IX0, IY0 = -(EXT + C), -C
IX1, IY1 =  BW + C,     BH + C
# tongue / relief offsets from board
def off(o):                       # (x0,y0,x1,y1) at outward offset o (extended -X)
    return (-(EXT + o), -o, BW + o, BH + o)

def rad_of(o):                    # corner radius of a feature at offset o
    return max(BR + o, 0.4)
O_IN  = C
O_TNG = C + PV["tongue_t"]
O_REL = C + PV["tongue_t"] + PV["lap_fit"]
bead_z = seam_z + (PV["lap"] - PV["bead_h"]) / 2.0    # snap bead/groove centre in the lap band

# =====================================================================
# HELPERS
# =====================================================================
def find_edges(feat, axis):
    out = []
    for i, e in enumerate(feat.Shape.Edges):
        vs = e.Vertexes
        if len(vs) != 2:
            continue
        p1, p2 = vs[0].Point, vs[1].Point
        if axis == "vertical":
            if abs(p1.x-p2.x) < 1e-3 and abs(p1.y-p2.y) < 1e-3 and abs(p1.z-p2.z) > 0.5:
                out.append(f"Edge{i+1}")
        elif axis == "top":
            if abs(p1.z-p2.z) < 1e-3 and p1.z > base_top_z - 1e-2:
                out.append(f"Edge{i+1}")
        elif axis == "front":
            if abs(p1.z-p2.z) < 1e-3 and p1.z < front_outer_z + 1e-2:
                out.append(f"Edge{i+1}")
    return out

def rect_sketch(body, name, z, x0, y0, x1, y1):
    """Constrained rectangle on XY at height z."""
    sk = body.newObject("Sketcher::SketchObject", name)
    sk.AttachmentSupport = [(body.Origin.OriginFeatures[3], "")]
    sk.MapMode = "FlatFace"
    sk.AttachmentOffset = App.Placement(V(0, 0, z), ROT0)
    g = sk.GeometryCount
    sk.addGeometry(Part.LineSegment(V(x0,y0,0), V(x1,y0,0)), False)
    sk.addGeometry(Part.LineSegment(V(x1,y0,0), V(x1,y1,0)), False)
    sk.addGeometry(Part.LineSegment(V(x1,y1,0), V(x0,y1,0)), False)
    sk.addGeometry(Part.LineSegment(V(x0,y1,0), V(x0,y0,0)), False)
    for k in range(4):
        sk.addConstraint(Sketcher.Constraint("Coincident", g+k, 2, g+(k+1) % 4, 1))
    sk.addConstraint(Sketcher.Constraint("Horizontal", g))
    sk.addConstraint(Sketcher.Constraint("Horizontal", g+2))
    sk.addConstraint(Sketcher.Constraint("Vertical", g+1))
    sk.addConstraint(Sketcher.Constraint("Vertical", g+3))
    DOCO.recompute()
    return sk

def _add_rrect(sk, x0, y0, x1, y1, r):
    """Add one ROUNDED-rectangle wire (4 lines + 4 arcs) to a sketch."""
    r = max(min(r, (x1-x0)/2 - 1e-3, (y1-y0)/2 - 1e-3), 0.05)
    g = sk.GeometryCount
    A = Part.ArcOfCircle
    Ci = lambda cx, cy: Part.Circle(V(cx, cy, 0), V(0, 0, 1), r)
    rad = math.radians
    sk.addGeometry(Part.LineSegment(V(x0+r,y0,0), V(x1-r,y0,0)), False)   # 0 bottom
    sk.addGeometry(Part.LineSegment(V(x1,y0+r,0), V(x1,y1-r,0)), False)   # 1 right
    sk.addGeometry(Part.LineSegment(V(x1-r,y1,0), V(x0+r,y1,0)), False)   # 2 top
    sk.addGeometry(Part.LineSegment(V(x0,y1-r,0), V(x0,y0+r,0)), False)   # 3 left
    sk.addGeometry(A(Ci(x1-r,y0+r), rad(-90), rad(0)),   False)          # 4 BR
    sk.addGeometry(A(Ci(x1-r,y1-r), rad(0),  rad(90)),   False)          # 5 TR
    sk.addGeometry(A(Ci(x0+r,y1-r), rad(90), rad(180)),  False)          # 6 TL
    sk.addGeometry(A(Ci(x0+r,y0+r), rad(180),rad(270)),  False)          # 7 BL
    C = Sketcher.Constraint
    for a, b in [(0,4),(4,1),(1,5),(5,2),(2,6),(6,3),(3,7),(7,0)]:
        sk.addConstraint(C("Coincident", g+a, 2, g+b, 1))

def frame_sketch(body, name, z, o_out, o_in):
    """Rounded-rectangle FRAME (outer + inner island) -> pad/pocket.
       Corners follow the case fillet (radius = board_r + offset) so frame
       features never poke out past the rounded walls."""
    sk = body.newObject("Sketcher::SketchObject", name)
    sk.AttachmentSupport = [(body.Origin.OriginFeatures[3], "")]
    sk.MapMode = "FlatFace"
    sk.AttachmentOffset = App.Placement(V(0, 0, z), ROT0)
    _add_rrect(sk, *off(o_out), rad_of(o_out))
    _add_rrect(sk, *off(o_in),  rad_of(o_in))
    DOCO.recompute()
    return sk

def sub_box(body, name, x0, y0, z0, dx, dy, dz, L=None, Wd=None, H=None):
    b = body.newObject("PartDesign::SubtractiveBox", name)
    b.Length, b.Width, b.Height = dx, dy, dz
    b.Placement = App.Placement(V(x0, y0, z0), ROT0)
    if L:  b.setExpression("Length", L)
    if Wd: b.setExpression("Width",  Wd)
    if H:  b.setExpression("Height", H)
    DOCO.recompute()
    return b

def add_box(body, name, x0, y0, z0, dx, dy, dz):
    b = body.newObject("PartDesign::AdditiveBox", name)
    b.Length, b.Width, b.Height = dx, dy, dz
    b.Placement = App.Placement(V(x0, y0, z0), ROT0)
    DOCO.recompute()
    return b

def add_cyl(body, name, cx, cy, z0, r, h):
    c = body.newObject("PartDesign::AdditiveCylinder", name)
    c.Radius, c.Height = r, h
    c.Placement = App.Placement(V(cx, cy, z0), ROT0)
    DOCO.recompute()
    return c

def sub_cyl(body, name, cx, cy, z0, r, h):
    c = body.newObject("PartDesign::SubtractiveCylinder", name)
    c.Radius, c.Height = r, h
    c.Placement = App.Placement(V(cx, cy, z0), ROT0)
    DOCO.recompute()
    return c

def fillet(body, name, base, edges, radius, expr=None):
    f = body.newObject("PartDesign::Fillet", name)
    f.Base = (base, edges)
    f.Radius = radius
    if expr:
        f.setExpression("Radius", expr)
    DOCO.recompute()
    return f

def zface(feat, ztarget):
    """Name of the planar face whose normal is +/-Z at height ztarget."""
    for i, f in enumerate(feat.Shape.Faces):
        if abs(f.CenterOfMass.z - ztarget) < 1e-3 \
           and isinstance(f.Surface, Part.Plane) and abs(f.Surface.Axis.z) > 0.9:
            return f"Face{i+1}"
    return None

def shell_open_at(body, name, base, ztarget):
    """PartDesign Thickness shell, opening the planar face at ztarget."""
    face = zface(base, ztarget)
    if not face:
        return base
    th = body.newObject("PartDesign::Thickness", name)
    th.Base = (base, [face])
    th.Value = W
    th.Reversed = True
    th.setExpression("Value", SP("wall"))
    DOCO.recompute()
    return th

def frame_pad(body, name, z, length, o_out, o_in, expr=None):
    sk = frame_sketch(body, name+"_Sk", z, o_out, o_in)
    p = body.newObject("PartDesign::Pad", name)
    p.Profile = sk
    p.Length = length
    if expr: p.setExpression("Length", expr)
    DOCO.recompute()
    return p

def frame_pocket(body, name, z, length, o_out, o_in, expr=None, reversed_=True):
    sk = frame_sketch(body, name+"_Sk", z, o_out, o_in)
    p = body.newObject("PartDesign::Pocket", name)
    p.Profile = sk
    p.Length = length
    p.Reversed = reversed_          # cut +Z (into the material above the seam)
    if expr: p.setExpression("Length", expr)
    DOCO.recompute()
    return p

def snap_spots():
    """(cx, cy, wall) snap-bead positions: N per long wall, 1 on -X (centre), and
       on +X two clips FLANKING the USB-C port (so they don't hit the opening)."""
    n = int(PV["snap_n_long"]); s = []
    for i in range(n):
        cx = BW * (i + 1) / (n + 1)
        s += [(cx, None, '-y'), (cx, None, '+y')]
    s += [(None, BH * 0.5, '-x')]
    off_usb = PV["usb_w"] / 2 + PV["snap_w"] / 2 + 1.2     # clear of the port + margin
    s += [(None, PV["usb_cy"] - off_usb, '+x'), (None, PV["usb_cy"] + off_usb, '+x')]
    return s

def add_snap_beads(body):
    """Discrete snap beads on the front tongue: protrude past the relief wall so
       the thin tongue flexes and clicks into the backplate recesses (inside the
       lap -> no added case thickness). A top lead-in chamfer eases assembly."""
    proj, sw, bh, lead = PV["bead_proj"], PV["snap_w"], PV["bead_h"], PV["bead_lead"]
    for j, (cx, cy, wall) in enumerate(snap_spots()):
        if wall == '-y':   b = add_box(body, f"Bead_FC_{j}", cx-sw/2, -(O_TNG+proj), bead_z, sw, proj, bh)
        elif wall == '+y': b = add_box(body, f"Bead_FC_{j}", cx-sw/2, BH+O_TNG,     bead_z, sw, proj, bh)
        elif wall == '-x': b = add_box(body, f"Bead_FC_{j}", -(EXT+O_TNG+proj), cy-sw/2, bead_z, proj, sw, bh)
        else:              b = add_box(body, f"Bead_FC_{j}", BW+O_TNG,     cy-sw/2, bead_z, proj, sw, bh)
        # lead-in: chamfer the bead's TOP outer edge (leading edge on assembly)
        ztop = bead_z + bh
        if wall in ('-y', '+y'):
            yo = -(O_TNG+proj) if wall == '-y' else BH+O_TNG+proj
            ce = [f"Edge{i+1}" for i, e in enumerate(b.Shape.Edges)
                  if all(abs(v.Point.z-ztop) < 1e-3 and abs(v.Point.y-yo) < 1e-3 for v in e.Vertexes)]
        else:
            xo = -(EXT+O_TNG+proj) if wall == '-x' else BW+O_TNG+proj
            ce = [f"Edge{i+1}" for i, e in enumerate(b.Shape.Edges)
                  if all(abs(v.Point.z-ztop) < 1e-3 and abs(v.Point.x-xo) < 1e-3 for v in e.Vertexes)]
        if ce:
            try:
                ch = body.newObject("PartDesign::Chamfer", f"BeadLead_{j}")
                ch.Base = (b, ce); ch.Size = min(lead, bh-0.2, proj-0.05)
                DOCO.recompute()
                if not ch.Shape.isValid():
                    body.removeObject(ch); DOCO.recompute()
            except Exception:
                pass

def add_snap_recesses(body):
    """Matching BLIND recesses in the backplate relief wall that capture the
       beads. Depth = only the bead's protrusion past the relief wall (+0.1 mm),
       so a solid outer skin remains -> doesn't cut through the curved back wall."""
    sw, bh, pad = PV["snap_w"], PV["bead_h"], 0.4
    rec_d = (PV["bead_proj"] - PV["lap_fit"]) + 0.1     # just enough for the bead to seat
    for j, (cx, cy, wall) in enumerate(snap_spots()):
        if wall == '-y':   sub_box(body, f"Recess_BP_{j}", cx-sw/2-pad, -(O_REL+rec_d), bead_z-pad, sw+2*pad, rec_d, bh+2*pad)
        elif wall == '+y': sub_box(body, f"Recess_BP_{j}", cx-sw/2-pad, BH+O_REL,        bead_z-pad, sw+2*pad, rec_d, bh+2*pad)
        elif wall == '-x': sub_box(body, f"Recess_BP_{j}", -(EXT+O_REL+rec_d), cy-sw/2-pad, bead_z-pad, rec_d, sw+2*pad, bh+2*pad)
        else:              sub_box(body, f"Recess_BP_{j}", BW+O_REL,        cy-sw/2-pad, bead_z-pad, rec_d, sw+2*pad, bh+2*pad)

# =====================================================================
# DOCUMENT + SPREADSHEET
# =====================================================================
if DOC in [d.Name for d in App.listDocuments().values()]:
    App.closeDocument(DOC)
DOCO = App.newDocument(DOC)

sheet = DOCO.addObject("Spreadsheet::Sheet", "Parameters")
sheet.set("A1", "Parameter"); sheet.set("B1", "Value"); sheet.set("C1", "Description")
for i, (alias, val, desc) in enumerate(PARAMS, start=2):
    sheet.set(f"A{i}", alias)
    sheet.set(f"B{i}", str(val))
    sheet.set(f"C{i}", desc)
    try: sheet.setAlias(f"B{i}", alias)
    except Exception: pass
DOCO.recompute()

# =====================================================================
# FRONT PLATE (deep tray: screen + PCB on an internal ledge + all cutouts)
# =====================================================================
def build_front_cover():
    body = DOCO.addObject("PartDesign::Body", "FrontCover")
    # 1. outer block front_outer_z -> seam (top, above the Pico)
    sk = rect_sketch(body, "Sk_FC", front_outer_z, OX0, OY0, OX1, OY1)
    pad = body.newObject("PartDesign::Pad", "Pad_FC")
    pad.Profile = sk
    pad.Length = seam_z - front_outer_z
    pad.setExpression("Length", f"{SP('screen_top')} + {SP('ftop')}")
    DOCO.recompute()
    # 2. corner fillet  3. aggressive front-edge curve
    last = fillet(body, "Fillet_FC_Corners", pad, find_edges(pad, "vertical"),
                  PV["corner_r"], SP("corner_r"))
    fe = find_edges(last, "front")
    if fe:
        last = fillet(body, "Fillet_FC_Front", last, fe, PV["front_curve"], SP("front_curve"))
    # 4. constant-wall curved shell, open at the +Z/seam top
    last = shell_open_at(body, "Shell_FC", last, seam_z)
    # 5. PCB ledge padded DOWN into a structural side rib that runs to the front
    #    floor and MESHES with the curved wall: below the curve the straight-
    #    position rib outer falls inside the inward-curving wall, so it merges
    #    (no gap, no overhang, no poke-through). Top = Z0 (PCB rests here).
    ld = PV["ledge_depth"]
    ledge = frame_pad(body, "Pad_FC_Ledge", -ld, ld, O_IN, O_IN - PV["ledge_in"], SP("ledge_depth"))
    lth = ld   # downstream cuts (battery gap, drill notches) clear the full rib
    # carve the SCREEN space so the rib clears the screen on the -X (screen) edge
    sx0, sx1, sy0, sy1 = -0.40, 71.60, 6.10, 36.10        # screen module footprint
    scr_front = front_outer_z + W                          # screen front face
    sub_box(body, "Cut_FC_ScreenClear", sx0-0.3, sy0-0.3, front_floor_inner,
            (sx1-sx0)+0.6, (sy1-sy0)+0.6, (scr_front+2.0)-front_floor_inner)
    # 6. screen window (sized inside the screw holes)
    sub_box(body, "Cut_FC_Window", PV["win_x0"], PV["win_y0"], front_outer_z-1.0,
            PV["win_x1"]-PV["win_x0"], PV["win_y1"]-PV["win_y0"], W+2.0,
            L=f"{SP('win_x1')} - {SP('win_x0')}", Wd=f"{SP('win_y1')} - {SP('win_y0')}")
    # 7. round joystick boss (5 mm, annular fill around the hole)
    add_cyl(body, "Boss_FC_Joy", PV["joy_cx"], PV["joy_cy"], front_outer_z,
            PV["joy_boss_d"]/2, PV["joy_pad_th"])
    # (USB-C + switch live in the backplate now)
    # 10. battery-connector / cable gap (CN1, -Y): a blind pocket from the inside
    #     that reaches DOWN into the curved front-bottom for cable routing, but
    #     leaves `bat_floor` of solid front skin (a printable first layer). Starts
    #     at the wall inner so the outer wall stays solid.
    bat_z0 = front_outer_z + PV["bat_floor"]
    sub_box(body, "Cut_FC_BatteryGap",
            PV["bat_cx"]-PV["bat_gap_w"]/2, IY0, bat_z0,
            PV["bat_gap_w"], PV["bat_gap_d"], (1.0)-bat_z0,
            L=SP("bat_gap_w"))
    # 10b. notch the rib around the 2 mount holes closest to the Y axis (x=2.4)
    for i, (hx, hy) in enumerate(sorted(EINK_HOLES, key=lambda h: h[0])[:2]):
        sub_box(body, f"Cut_FC_DrillNotch{i}", IX0, hy-4.0, -ld-0.2,
                (hx+3.0)-IX0, 8.0, ld+0.7)
    # 11. lap tongue (rounded frame) with all-around clearance + snap bead
    fit = PV["lap_fit"]
    frame_pad(body, "Pad_FC_Tongue", seam_z, PV["lap"] - fit, O_TNG, O_IN + fit,
              f"{SP('lap')} - {SP('lap_fit')}")
    add_snap_beads(body)
    # 11b. USB-C clearance: remove the +X tongue where the connector overhangs the
    #      board edge and dips to Z=0.67 (sits between the two flanking snaps)
    sub_box(body, "Cut_FC_USB", BW+C-1.0, PV["usb_cy"]-PV["usb_w"]/2-0.6, 0.0,
            W+C+3.0, PV["usb_w"]+1.2, PV["lap"]+1.0,
            Wd=f"{SP('usb_w')} + 1.2")
    # 11c. power-switch clearance: remove the -Y tongue at the switch so it doesn't
    #      hit the switch actuator when the case is mated
    sub_box(body, "Cut_FC_Switch", PV["sw_x0"]-0.5, -(C+W)-1.0, 0.0,
            (PV["sw_x1"]-PV["sw_x0"])+1.0, W+C+2.0, PV["lap"]+1.0)
    # 12. joystick through-hole
    sub_cyl(body, "Cut_FC_Joy", PV["joy_cx"], PV["joy_cy"], front_outer_z-1.0,
            PV["joy_hole_d"]/2, PV["screen_top"]+PV["ftop"]+2.0)
    return body

# =====================================================================
# BACKPLATE  (deep cover: houses USB-C + Pico, curved closed back, clips on)
# =====================================================================
def build_backplate():
    body = DOCO.addObject("PartDesign::Body", "BackPlate")
    # 1. block seam(0) -> base_top
    sk = rect_sketch(body, "Sk_BP", seam_z, OX0, OY0, OX1, OY1)
    pad = body.newObject("PartDesign::Pad", "Pad_BP")
    pad.Profile = sk
    pad.Length = base_top_z - seam_z
    pad.setExpression("Length", SP("back_above"))
    DOCO.recompute()
    # 2. corner fillet  3. back-edge curve (same as the front)
    last = fillet(body, "Fillet_BP_Corners", pad, find_edges(pad, "vertical"),
                  PV["corner_r"], SP("corner_r"))
    te = find_edges(last, "top")
    if te:
        last = fillet(body, "Fillet_BP_Back", last, te, PV["back_curve"], SP("back_curve"))
    # 4. constant-wall curved shell, open at the seam (toward the front plate)
    last = shell_open_at(body, "Shell_BP", last, seam_z)
    # 5. lap relief (frame): receives the front-plate tongue
    frame_pocket(body, "Cut_BP_Relief", seam_z, PV["lap"], O_REL, O_IN, SP("lap"))
    # 6. snap recesses (capture the front-plate beads)
    add_snap_recesses(body)
    # 7. USB-C opening (+X)
    sub_box(body, "Cut_BP_USB", BW+C-1.0, PV["usb_cy"]-PV["usb_w"]/2, PV["usb_z0"],
            W+C+3.0, PV["usb_w"], PV["usb_z1"]-PV["usb_z0"],
            Wd=SP("usb_w"), H=f"{SP('usb_z1')} - {SP('usb_z0')}")
    # 8. power-switch slot (-Y)
    sub_box(body, "Cut_BP_Switch", PV["sw_x0"], -(C+W)-1.0, PV["sw_z0"],
            PV["sw_x1"]-PV["sw_x0"], W+2.0, PV["sw_z1"]-PV["sw_z0"],
            L=f"{SP('sw_x1')} - {SP('sw_x0')}", H=f"{SP('sw_z1')} - {SP('sw_z0')}")
    return body

# =====================================================================
# THUMBPIECE
# =====================================================================
def build_thumbpiece():
    body = DOCO.addObject("PartDesign::Body", "Thumbpiece")
    cx, cy = PV["joy_cx"], PV["joy_cy"]
    bot = front_outer_z + 0.10
    disc = add_cyl(body, "Thumb_Disc", cx, cy, bot, PV["thumb_od"]/2, PV["thumb_h"])
    disc.setExpression("Radius", f"{SP('thumb_od')} / 2")
    disc.setExpression("Height", SP("thumb_h"))
    DOCO.recompute()
    sph = body.newObject("PartDesign::SubtractiveSphere", "Thumb_Dish")
    sph.Radius = PV["thumb_dish_r"]
    sph.Placement = App.Placement(V(cx, cy, bot - PV["thumb_dish_r"] + PV["thumb_dish_d"]), ROT0)
    sph.setExpression("Radius", SP("thumb_dish_r"))
    DOCO.recompute()
    s = PV["thumb_sock"]
    top = bot + PV["thumb_h"]
    sub_box(body, "Thumb_Socket", cx-s/2, cy-s/2, top-PV["thumb_sock_d"], s, s, PV["thumb_sock_d"]+0.1)
    return body

# =====================================================================
# IMPORT ASSEMBLY (reference)
# =====================================================================
def import_assembly():
    path = "/home/rompasaurus/COdingProjects/Dilder-PCB/Case Design/Dilder_PCB_FullAssembly.step"
    if not os.path.exists(path):
        return None
    raw = Part.Shape(); raw.read(path)
    raw.translate(V(-46.70, 88.00, 0.0))
    dz = (front_outer_z + W) - (-8.64)
    kept = []
    for s in raw.Solids:
        b = s.BoundBox
        if b.ZMax > 6.0:
            continue
        cx, cy = (b.XMin+b.XMax)/2, (b.YMin+b.YMax)/2
        if b.ZMax < -5.0 and -2 < cx < 73 and 4 < cy < 38:
            t = s.copy(); t.translate(V(0, 0, dz)); kept.append(t)
        else:
            kept.append(s)
    obj = DOCO.addObject("Part::Feature", "Dilder_Assembly")
    obj.Shape = Part.makeCompound(kept)
    if GUI and obj.ViewObject:
        obj.ViewObject.ShapeColor = (0.55, 0.55, 0.58)
    return obj

# =====================================================================
# RUN
# =====================================================================
bp = build_backplate()
fc = build_front_cover()
tp = build_thumbpiece()
asm = import_assembly()
DOCO.recompute()

if GUI:
    for b, col in [(bp,(0.30,0.55,0.85)), (fc,(0.85,0.55,0.30)), (tp,(0.15,0.15,0.18))]:
        try: b.ViewObject.ShapeColor = col
        except Exception: pass

here = os.path.dirname(os.path.abspath(__file__)) if "__file__" in globals() else os.getcwd()
proj = os.path.dirname(here) if os.path.basename(here) == "freecad" else here
DOCO.saveAs(os.path.join(here, "WetGregCase.FCStd"))
exp = os.path.join(proj, "exports")
try:
    os.makedirs(exp, exist_ok=True)
    Part.export([bp], os.path.join(exp, "WetGregCase_BackPlate.step"))
    Part.export([fc], os.path.join(exp, "WetGregCase_FrontCover.step"))
    Part.export([tp], os.path.join(exp, "WetGregCase_Thumbpiece.step"))
except Exception as e:
    App.Console.PrintWarning("STEP export skipped: %s\n" % e)
try:                                   # print-ready 3MF meshes (regenerated each run)
    import Mesh
    for o, nm in [(fc, "FrontCover"), (bp, "BackPlate"), (tp, "Thumbpiece")]:
        Mesh.export([o], os.path.join(here, "WetGregCase-%s.3mf" % nm))
except Exception as e:
    App.Console.PrintWarning("3MF export skipped: %s\n" % e)

def chk(b):
    s = b.Shape
    return f"solids={len(s.Solids)} valid={s.isValid()} closed={s.isClosed()}"
print("="*62)
print("WetGregCase (PartDesign + Parameters spreadsheet)")
print("  BackPlate :", chk(bp))
print("  FrontCover:", chk(fc))
print("  Thumbpiece:", chk(tp))
print("  Overall Z : %.2f .. %.2f (%.2f mm)" % (front_outer_z, base_top_z, base_top_z-front_outer_z))
print("="*62)

if GUI:
    try:
        import FreeCADGui as Gui
        Gui.activeDocument().activeView().viewIsometric()
        Gui.SendMsgToActiveView("ViewFit")
    except Exception:
        pass

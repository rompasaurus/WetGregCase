"""
WetGregCase — Parametric PartDesign Enclosure for the Dilder PCB
===============================================================
Proper PartDesign model (like dilder_rev2_mk2): every part is a Body built
from a constrained sketch + Pad / Pocket / Fillet / Thickness / primitive
chain, with ALL key dimensions driven by the "Parameters" spreadsheet.

  * Edit any cell in the Parameters sheet and press Ctrl+Shift+R to recompute.
  * Add or adjust fillets/chamfers directly on the feature tree in the GUI.
  * Clean B-rep solids (no fused-primitive overlaps) -> slice cleanly for print.

Bodies:
  BackPlate   — board carrier: wraps the board edge, PCB rests on a shelf,
                closed back panel (clears the Pico), curved back edge.
  FrontCover  — screen lid: constant-wall curved shell, screen window sized
                inside the screw holes, round joystick boss, lap tongue.
  Thumbpiece  — snap cap over the 5-way joystick.
  Dilder_Assembly — imported KiCad STEP (reference; headers stripped, screen
                aligned to the front face).

Frame: local = (KiCad_X - 46.70, KiCad_StepY + 88.0, Z); Z=0 = PCB bottom.

Run:  FreeCAD > Macro > Run, or `freecadcmd wetgreg_case.FCMacro`
"""

import math, os
import FreeCAD as App
import Part
import Sketcher

V = App.Vector
ROT0 = App.Rotation()
GUI = App.GuiUp
DOC = "WetGregCase"

# =====================================================================
# PARAMETERS  (alias, value, description)  -> Parameters spreadsheet
# =====================================================================
PARAMS = [
    # --- Board (from KiCad) ---
    ("board_w",   96.80, "Board width X (1 mm shorter than the KiCad nominal)"),
    ("board_h",   42.012,"Board height Y"),
    ("board_t",    1.47, "PCB thickness (real, from STEP)"),
    ("board_rest_z",2.10, "Board bottom rests at the bead top (FLUSH): the board sits ON the bead, lifting the USB-C base clear of the tongue so NO USB relief is needed and the bead fully connects"),
    ("board_r",    5.00, "Board corner radius"),
    # --- Fit / walls ---
    ("clear",      0.30, "PCB-to-wall clearance per side"),
    ("wall",       2.40, "Wall thickness (+0.4 for snap-bead rigidity)"),
    ("ext_xmin",   0.30, "Case extension on -X past the board edge: sized so the -X wall clears the screen overhang (-0.394) by 0.2mm wiggle (cavity inner = -0.6)"),
    ("ext_y",      0.00, "Long-side (±Y) wall push-out PER SIDE. Set back to 0 (was 0.5): the +0.5/side widening gave the Dilder PCB too much Y wiggle, so the cavity is brought back in to the board edge."),
    ("corner_r",   7.70, "Outer corner radius (board_r+clear+wall = 5+0.3+2.4)"),
    # --- Screen side (-Z, front lid) ---
    ("screen_top", 11.83,"Front-cover depth so the window inner meets the real screen front (-9.43): 13mm screen-to-PCB-backside stack. = wall - (board_rest_z + board_t - 13)."),
    ("screen_cal", -2.89,"Screen Z calibration: STEP model placed the screen 2.89mm too close; this shifts it out to the real 13mm top-of-screen-to-PCB-backside stack (- = away from board)"),
    ("screen_back", -5.30,"Real screen back face Z (+0.3 clear): rib is carved away below this in the screen footprint so it clears the screen; rib above it supports the PCB"),
    ("front_curve",6.00, "Front-edge curve radius (was 6.0; halved for a boxier look, matches back_curve)"),
    # --- Seam / backplate (deep cover that clips onto the front lid) ---
    ("ftop",       0.00, "Front-plate top / seam Z (= PCB rest / mating face)"),
    ("back_above", 9.10, "Backplate depth above the seam (net -1mm from the Pico-block max: removes most dead space but keeps 1mm headroom)."),
    ("back_skim",  1.00, "Skim off the OUTER back face (thinner back panel -> see through the translucent back better); inner cavity unchanged"),
    ("back_curve", 6.00, "Back-edge curve radius (was 6.0; halved for a boxier look, matches front_curve)"),
    # --- PCB ledge inside the FRONT plate (walls come in to support the board) ---
    ("ledge_in",   2.00, "Ledge reach in from the wall (board rests on it)"),
    ("ledge_th",   1.20, "Ledge thickness"),
    ("ledge_depth",11.53,"Ledge rib depth = pcb_rest_z + screen_top - wall: runs from the board rest down to the front floor, merging with the curved wall"),
    ("shelf_w",    1.60, "(legacy) board-edge reach"),
    ("back_shelf_reach", 2.50, "Back perimeter shelf reach in from the wall (clamps the board top edge)"),
    ("standoff_clr",     2.50, "Clearance radius at each M2 standoff hole (front + back notches)"),
    ("scr_carve_in",     1.00, "Extra screen-clearance carved into the inner -X wall (board/screen fit)"),
    # --- Battery connector gap (CN1 on the screen side) ---
    ("bat_cx",    41.50, "Battery connector CN1 centre X"),
    ("bat_cy",     2.50, "Battery connector CN1 centre Y"),
    ("bat_gap_w", 13.00, "Battery connector / cable gap width"),
    ("bat_gap_d",  7.00, "Battery gap depth into the board (stays below the window)"),
    ("bat_floor",  2.40, "Solid front skin left under the battery gap (>= wall, keeps the front floor whole + printable)"),
    # --- Battery body + printed corner clips (innCraft 503450 LiPo) ---
    ("bat_body_x", 51.00, "Battery body size X (innCraft 503450 pouch, 51x34x5)"),
    ("bat_body_y", 34.00, "Battery body size Y"),
    ("bat_body_z",  5.00, "Battery body thickness Z (critical PCB-to-screen stack-up)"),
    ("bat_ctr_x",  35.80, "Battery centre X (shifted -4mm total from the KiCad 39.8 to give the e-ink header connector room on the +X end)"),
    ("bat_ctr_y",  23.00, "Battery centre Y in case-local frame (KiCad 65.0 -> 88.0-Y)"),
    # two end-clips: each hooks the two M2 standoff pillars at one X-end of the battery
    # via open notches, and walls the battery's two corners there, height = cell thickness.
    ("clip_fit",    0.40, "Clip clearance to the battery edges and to the standoff pillars"),
    ("clip_wall",   2.00, "Clip wall thickness (battery-edge rail + corner returns + pillar-tab flanks)"),
    ("clip_pillar_r",2.10,"Standoff pillar radius the clip notch/hole cups (= standoff_d/2; +1mm wider holes/slot to fit the real ~4mm standoffs)"),
    ("clip_return", 7.00, "Clip corner-return length along the battery edge (Y-stop reach)"),
    ("clip_lip_proj",3.00,"Z-retention overhang: inward reach over the battery corners (holds the cell)"),
    ("clip_lip_th",  1.00,"Z-retention overhang thickness (layer under the cell that traps it against the PCB)"),
    # --- M2 brass standoffs holding the e-ink screen off the PCB (assembly reference) ---
    ("standoff_h",  10.00, "Brass standoff length (M2 x 10mm): screen back sits this far off the PCB screen-side face"),
    ("standoff_d",   4.20, "Standoff body diameter (measured a smidge over 4mm) the clips cup"),
    # --- Flush lap joint + discrete snap-fit (inside the lap; no added thickness) ---
    ("lap",        4.50, "Lap tongue height (engagement; lives inside the backplate). Sized so tongue top (lap-lap_fit=4.3) still covers the raised bead top (4.2)."),
    ("tongue_t",   1.00, "Tongue thickness (thin -> flexes to snap)"),
    ("lap_fit",    0.20, "Tongue-to-relief slip gap"),
    ("bead_proj",  0.60, "Snap bead projection past the tongue (interference = proj-lap_fit = 0.4): eased from 0.8 -> 0.6 because 0.6mm interference took too much force and cracked the backplate."),
    ("bead_h",     1.10, "Snap bead height (Z): shaved 0.5 (was 1.6) so it eases in/out without snapping off. Base at lock_lip (1.0), top at 2.1, under the tongue top (4.3)."),
    ("bead_lead",  0.80, "Snap bead lead-in (top chamfer = leading edge on assembly)"),
    ("snap_w",     6.00, "Snap bead width along the wall"),
    ("lock_lip",   1.00, "Solid uninterrupted lip (Z) at the seam entry of the backplate relief wall, BELOW the bead. No cutout runs through it, so the bead must flex PAST it to seat -> it locks behind the lip (cantilever snap). The bead base is raised to seam+lock_lip."),
    # --- Screen window (sized inside the 4 M2 screw holes) ---
    ("win_x0",    11.60, "Window X min (extended 1mm toward the Y axis)"),
    ("win_x1",    63.60, "Window X max (long edge shaved 2mm; long edges 4mm shorter)"),
    ("win_y0",     8.10, "Window Y min (+1mm in: centres the screen in Y)"),
    ("win_y1",    35.10, "Window Y max (1mm shy of screen PCB)"),
    # --- USB-C opening (+X) ---
    ("usb_cy",    21.00, "USB-C centre Y"),
    ("usb_w",      9.70, "USB-C opening width Y"),
    ("usb_z0",     0.00, "USB-C opening Z bottom (= lip top)"),
    ("usb_z1",     7.20, "USB-C opening Z top (connector now reaches ~7.0 after board_rest_z; keep above that, below cap top 9.8)."),
    ("usb_r",      1.00, "USB-C opening corner radius"),
    ("usb_lip_h",  2.10, "Front-cover outer lip height at the USB notch = bead top: the lip meets the top of the bead (connector now sits above the bead)."),
    # --- Power slide switch MSK12C02 (SPDT 8x2.8x1.4) on -Y: NO external opening/slider ---
    # A blind pocket from the inside clears the actuator; the outer -Y face stays closed
    # by a single printed skin (sw_skin), so the board still drops flush onto the shelf.
    ("sw_cx",     50.55, "Switch actuator centre X (mid-travel)"),
    ("sw_pocket_w", 5.10, "Switch pocket width X (actuator + full travel + clearance; = old slot)"),
    ("sw_pocket_z0",0.70, "Switch pocket Z bottom (above board rest)"),
    ("sw_pocket_z1",3.60, "Switch pocket Z top (above board rest)"),
    ("sw_skin",     1.00, "Outer -Y skin left over the switch pocket (1.0mm: 0.4 was too thin, the slicer dropped it and left a hole)"),
    # --- Joystick / boss / thumbpiece ---
    ("joy_cx",    81.55, "Joystick centre X"),
    ("joy_cy",    21.30, "Joystick centre Y"),
    ("joy_hole_d",12.10, "Joystick hole diameter (+0.1mm)"),
    ("joy_boss_d",20.00, "Joystick boss outer diameter"),
    ("joy_pad_th", 5.00, "Joystick boss thickness (solar-connector room)"),
    ("thumb_od",   9.50, "Thumb cap outer diameter (was 11.00; -1.5mm for fit tolerance)"),
    ("thumb_h",    7.50, "Thumb cap height (raised 3mm from 4.5; square socket depth unchanged - it's referenced from the top)"),
    ("thumb_dish_r",12.00,"Thumb dish sphere radius"),
    ("thumb_dish_d",0.60,"Thumb dish depth"),
    ("thumb_sock", 3.70, "Thumb socket (square) - was 3.30; +0.2mm clearance per side"),
    ("thumb_sock_d",3.50,"Thumb socket depth"),
    # --- snap-bead positions (fraction along each wall) ---
    ("snap_n_long", 2, "Snap beads per long wall"),
]
PV = {a: v for (a, v, _) in PARAMS}

def SP(alias):
    return f"Parameters.{alias}"

# Derived (literal positions; sizes/heights also live-bound below) ----
BW, BH, BT, BR = PV["board_w"], PV["board_h"], PV["board_t"], PV["board_r"]
C, W, EXT = PV["clear"], PV["wall"], PV["ext_xmin"]
EY = PV["ext_y"]                                  # ±Y wall push-out per side (long sides widened)
front_outer_z = -PV["screen_top"]                 # -11.4
front_floor_inner = front_outer_z + PV["wall"]    # -9.4 (front floor inner face)
seam_z        =  PV["ftop"]                        # 5.5  (front-plate top / clip seam, above the Pico)
base_top_z    =  seam_z + PV["back_above"]         # 7.5  (backplate cap top)
pcb_rest_z    =  PV["board_rest_z"]                # board bottom rests this high above the seam (above the bead)
board_top_z   =  pcb_rest_z + PV["board_t"]        # board backside (+Z); the back shelf clamps here
EINK_HOLES = [(2.4, 9.0), (2.4, 33.4), (68.8, 9.0), (68.8, 33.4)]   # M2 mount holes (local)
# outer footprint  (±Y pushed out by EY: long sides widened, walls + cavity follow)
OX0, OY0 = -(EXT + C + W), -(C + W + EY)
OX1, OY1 =  BW + C + W,     BH + C + W + EY
# inner cavity (board + clear, extended -X; ±Y also gains EY so the wall stays `wall` thick)
IX0, IY0 = -(EXT + C), -(C + EY)
IX1, IY1 =  BW + C,     BH + C + EY
# tongue / relief offsets from board (Y carries the EY push-out so the lap joint tracks the wall)
def off(o):                       # (x0,y0,x1,y1) at outward offset o (extended -X, widened ±Y)
    return (-(EXT + o), -(o + EY), BW + o, BH + o + EY)

def rad_of(o):                    # corner radius of a feature at offset o
    return max(BR + o, 0.4)
O_IN  = C
O_TNG = C + PV["tongue_t"]
O_REL = C + PV["tongue_t"] + PV["lap_fit"]
bead_z = seam_z + PV["lock_lip"]    # bead base sits lock_lip above the seam, leaving a solid uninterrupted lip below it that the bead snaps PAST -> the snap locks in place

# =====================================================================
# HELPERS
# =====================================================================
def find_edges(feat, axis):
    out = []
    for i, e in enumerate(feat.Shape.Edges):
        vs = e.Vertexes
        if len(vs) != 2:
            continue
        p1, p2 = vs[0].Point, vs[1].Point
        if axis == "vertical":
            if abs(p1.x-p2.x) < 1e-3 and abs(p1.y-p2.y) < 1e-3 and abs(p1.z-p2.z) > 0.5:
                out.append(f"Edge{i+1}")
        elif axis == "top":
            if abs(p1.z-p2.z) < 1e-3 and p1.z > base_top_z - 1e-2:
                out.append(f"Edge{i+1}")
        elif axis == "front":
            if abs(p1.z-p2.z) < 1e-3 and p1.z < front_outer_z + 1e-2:
                out.append(f"Edge{i+1}")
    return out

def rect_sketch(body, name, z, x0, y0, x1, y1):
    """Constrained rectangle on XY at height z."""
    sk = body.newObject("Sketcher::SketchObject", name)
    sk.AttachmentSupport = [(body.Origin.OriginFeatures[3], "")]
    sk.MapMode = "FlatFace"
    sk.AttachmentOffset = App.Placement(V(0, 0, z), ROT0)
    g = sk.GeometryCount
    sk.addGeometry(Part.LineSegment(V(x0,y0,0), V(x1,y0,0)), False)
    sk.addGeometry(Part.LineSegment(V(x1,y0,0), V(x1,y1,0)), False)
    sk.addGeometry(Part.LineSegment(V(x1,y1,0), V(x0,y1,0)), False)
    sk.addGeometry(Part.LineSegment(V(x0,y1,0), V(x0,y0,0)), False)
    for k in range(4):
        sk.addConstraint(Sketcher.Constraint("Coincident", g+k, 2, g+(k+1) % 4, 1))
    sk.addConstraint(Sketcher.Constraint("Horizontal", g))
    sk.addConstraint(Sketcher.Constraint("Horizontal", g+2))
    sk.addConstraint(Sketcher.Constraint("Vertical", g+1))
    sk.addConstraint(Sketcher.Constraint("Vertical", g+3))
    DOCO.recompute()
    return sk

def _add_rrect(sk, x0, y0, x1, y1, r):
    """Add one ROUNDED-rectangle wire (4 lines + 4 arcs) to a sketch."""
    r = max(min(r, (x1-x0)/2 - 1e-3, (y1-y0)/2 - 1e-3), 0.05)
    g = sk.GeometryCount
    A = Part.ArcOfCircle
    Ci = lambda cx, cy: Part.Circle(V(cx, cy, 0), V(0, 0, 1), r)
    rad = math.radians
    sk.addGeometry(Part.LineSegment(V(x0+r,y0,0), V(x1-r,y0,0)), False)   # 0 bottom
    sk.addGeometry(Part.LineSegment(V(x1,y0+r,0), V(x1,y1-r,0)), False)   # 1 right
    sk.addGeometry(Part.LineSegment(V(x1-r,y1,0), V(x0+r,y1,0)), False)   # 2 top
    sk.addGeometry(Part.LineSegment(V(x0,y1-r,0), V(x0,y0+r,0)), False)   # 3 left
    sk.addGeometry(A(Ci(x1-r,y0+r), rad(-90), rad(0)),   False)          # 4 BR
    sk.addGeometry(A(Ci(x1-r,y1-r), rad(0),  rad(90)),   False)          # 5 TR
    sk.addGeometry(A(Ci(x0+r,y1-r), rad(90), rad(180)),  False)          # 6 TL
    sk.addGeometry(A(Ci(x0+r,y0+r), rad(180),rad(270)),  False)          # 7 BL
    C = Sketcher.Constraint
    for a, b in [(0,4),(4,1),(1,5),(5,2),(2,6),(6,3),(3,7),(7,0)]:
        sk.addConstraint(C("Coincident", g+a, 2, g+b, 1))

def frame_sketch(body, name, z, o_out, o_in):
    """Rounded-rectangle FRAME (outer + inner island) -> pad/pocket.
       Corners follow the case fillet (radius = board_r + offset) so frame
       features never poke out past the rounded walls."""
    sk = body.newObject("Sketcher::SketchObject", name)
    sk.AttachmentSupport = [(body.Origin.OriginFeatures[3], "")]
    sk.MapMode = "FlatFace"
    sk.AttachmentOffset = App.Placement(V(0, 0, z), ROT0)
    _add_rrect(sk, *off(o_out), rad_of(o_out))
    _add_rrect(sk, *off(o_in),  rad_of(o_in))
    DOCO.recompute()
    return sk

def sub_box(body, name, x0, y0, z0, dx, dy, dz, L=None, Wd=None, H=None):
    b = body.newObject("PartDesign::SubtractiveBox", name)
    b.Length, b.Width, b.Height = dx, dy, dz
    b.Placement = App.Placement(V(x0, y0, z0), ROT0)
    if L:  b.setExpression("Length", L)
    if Wd: b.setExpression("Width",  Wd)
    if H:  b.setExpression("Height", H)
    DOCO.recompute()
    return b

def add_box(body, name, x0, y0, z0, dx, dy, dz):
    b = body.newObject("PartDesign::AdditiveBox", name)
    b.Length, b.Width, b.Height = dx, dy, dz
    b.Placement = App.Placement(V(x0, y0, z0), ROT0)
    DOCO.recompute()
    return b

def add_cyl(body, name, cx, cy, z0, r, h):
    c = body.newObject("PartDesign::AdditiveCylinder", name)
    c.Radius, c.Height = r, h
    c.Placement = App.Placement(V(cx, cy, z0), ROT0)
    DOCO.recompute()
    return c

def sub_cyl(body, name, cx, cy, z0, r, h):
    c = body.newObject("PartDesign::SubtractiveCylinder", name)
    c.Radius, c.Height = r, h
    c.Placement = App.Placement(V(cx, cy, z0), ROT0)
    DOCO.recompute()
    return c

def fillet(body, name, base, edges, radius, expr=None):
    f = body.newObject("PartDesign::Fillet", name)
    f.Base = (base, edges)
    f.Radius = radius
    if expr:
        f.setExpression("Radius", expr)
    DOCO.recompute()
    return f

def zface(feat, ztarget):
    """Name of the planar face whose normal is +/-Z at height ztarget."""
    for i, f in enumerate(feat.Shape.Faces):
        if abs(f.CenterOfMass.z - ztarget) < 1e-3 \
           and isinstance(f.Surface, Part.Plane) and abs(f.Surface.Axis.z) > 0.9:
            return f"Face{i+1}"
    return None

def shell_open_at(body, name, base, ztarget):
    """PartDesign Thickness shell, opening the planar face at ztarget."""
    face = zface(base, ztarget)
    if not face:
        return base
    th = body.newObject("PartDesign::Thickness", name)
    th.Base = (base, [face])
    th.Value = W
    th.Reversed = True
    th.setExpression("Value", SP("wall"))
    DOCO.recompute()
    return th

def frame_pad(body, name, z, length, o_out, o_in, expr=None):
    sk = frame_sketch(body, name+"_Sk", z, o_out, o_in)
    p = body.newObject("PartDesign::Pad", name)
    p.Profile = sk
    p.Length = length
    if expr: p.setExpression("Length", expr)
    DOCO.recompute()
    return p

def frame_pocket(body, name, z, length, o_out, o_in, expr=None, reversed_=True):
    sk = frame_sketch(body, name+"_Sk", z, o_out, o_in)
    p = body.newObject("PartDesign::Pocket", name)
    p.Profile = sk
    p.Length = length
    p.Reversed = reversed_          # cut +Z (into the material above the seam)
    if expr: p.setExpression("Length", expr)
    DOCO.recompute()
    return p

def snap_spots():
    """(cx, cy, wall) snap-bead positions: N per long wall, 1 on -X (centre), and
       on +X two clips FLANKING the USB-C port (so they don't hit the opening)."""
    n = int(PV["snap_n_long"]); s = []
    for i in range(n):
        cx = BW * (i + 1) / (n + 1)
        s += [(cx, None, '-y'), (cx, None, '+y')]
    s += [(None, BH * 0.5, '-x')]
    off_usb = PV["usb_w"] / 2 + PV["snap_w"] / 2 + 1.2     # clear of the port + margin
    s += [(None, PV["usb_cy"] - off_usb, '+x'), (None, PV["usb_cy"] + off_usb, '+x')]
    return s

def add_snap_beads(body):
    """CONTINUOUS snap bead: one uniform rib running ALL THE WAY AROUND the tongue's
       outer face (offset O_TNG), protruding past it by bead_proj. A lead-in chamfer
       runs along its top OUTER edge (the leading edge as the tongue inserts up) so it
       cams into the relief. Unbroken bead -> uniform engagement all around; replaces
       the old discrete beads + spot chamfers."""
    proj, bh, lead = PV["bead_proj"], PV["bead_h"], PV["bead_lead"]
    bead = frame_pad(body, "Bead_FC", bead_z, bh, O_TNG + proj, O_TNG, SP("bead_h"))
    # lead-in chamfer along the top OUTER edge loop (4 lines + 4 arcs), all around
    ztop = bead_z + bh
    def is_outer(v):                       # on the bead's OUTER perimeter (vs the inner loop)?
        x, y = v.Point.x, v.Point.y
        return (x <= -(EXT + O_TNG) - 0.1 or x >= BW + O_TNG + 0.1
                or y <= -(O_TNG + EY) - 0.1 or y >= BH + O_TNG + EY + 0.1)
    ce = [f"Edge{i+1}" for i, e in enumerate(bead.Shape.Edges)
          if len(e.Vertexes) and all(abs(v.Point.z - ztop) < 1e-3 for v in e.Vertexes)
          and all(is_outer(v) for v in e.Vertexes)]
    if ce:
        try:
            ch = body.newObject("PartDesign::Chamfer", "BeadLead")
            ch.Base = (bead, ce); ch.Size = min(lead, bh - 0.2, proj - 0.05)
            DOCO.recompute()
            if not ch.Shape.isValid():
                body.removeObject(ch); DOCO.recompute()
        except Exception:
            pass

def add_snap_recesses(body):
    """CONTINUOUS recess groove cut ALL AROUND the relief outer wall, capturing the
       continuous bead. Radial depth = the bead's protrusion past the relief (+0.1mm),
       so a solid outer skin remains (no cut through the curved back). The groove
       BOTTOM is flush with the bead base (bead_z), leaving the lock_lip below it
       solid -> the bead flexes past the lip and locks behind it (cantilever snap).
       One uniform groove; replaces the old discrete recesses."""
    bh, pad = PV["bead_h"], 0.4
    rec_d = (PV["bead_proj"] - PV["lap_fit"]) + 0.1     # just enough for the bead to seat
    # Extend the groove 0.5mm DOWN toward the seam (keeping the catching overhang at the
    # top): the bead reaches its recess ~0.5mm before full seating, riding that much less
    # lock-lip, so the backplate pairs/snaps instead of jamming. Lip drops 1.0 -> 0.5mm.
    seat = 0.5
    frame_pocket(body, "Recess_BP", bead_z - seat, bh + pad + seat, O_REL + rec_d, O_REL, reversed_=True)

# =====================================================================
# DOCUMENT + SPREADSHEET
# =====================================================================
if DOC in [d.Name for d in App.listDocuments().values()]:
    App.closeDocument(DOC)
DOCO = App.newDocument(DOC)

sheet = DOCO.addObject("Spreadsheet::Sheet", "Parameters")
sheet.set("A1", "Parameter"); sheet.set("B1", "Value"); sheet.set("C1", "Description")
for i, (alias, val, desc) in enumerate(PARAMS, start=2):
    sheet.set(f"A{i}", alias)
    sheet.set(f"B{i}", str(val))
    sheet.set(f"C{i}", desc)
    try: sheet.setAlias(f"B{i}", alias)
    except Exception: pass
DOCO.recompute()

# =====================================================================
# FRONT PLATE (deep tray: screen + PCB on an internal ledge + all cutouts)
# =====================================================================
def build_front_cover():
    body = DOCO.addObject("PartDesign::Body", "FrontCover")
    # 1. outer block front_outer_z -> seam (top, above the Pico). ALL FOUR outer walls
    #    are pushed out 0.2mm each: the snap beads splay the joint a touch on assembly
    #    (the short +/-X edges were bowing out on the backplate too), so the front lid is
    #    pre-grown to finish flush with the backplate.
    push = 0.20
    sk = rect_sketch(body, "Sk_FC", front_outer_z, OX0-push, OY0-push, OX1+push, OY1+push)
    pad = body.newObject("PartDesign::Pad", "Pad_FC")
    pad.Profile = sk
    pad.Length = seam_z - front_outer_z
    pad.setExpression("Length", f"{SP('screen_top')} + {SP('ftop')}")
    DOCO.recompute()
    # 2. corner fillet  3. aggressive front-edge curve
    last = fillet(body, "Fillet_FC_Corners", pad, find_edges(pad, "vertical"),
                  PV["corner_r"], SP("corner_r"))
    fe = find_edges(last, "front")
    if fe:
        last = fillet(body, "Fillet_FC_Front", last, fe, PV["front_curve"], SP("front_curve"))
    # 4. constant-wall curved shell, open at the +Z/seam top
    last = shell_open_at(body, "Shell_FC", last, seam_z)
    # 5. PCB ledge padded DOWN into a structural side rib that runs to the front
    #    floor and MESHES with the curved wall: below the curve the straight-
    #    position rib outer falls inside the inward-curving wall, so it merges
    #    (no gap, no overhang, no poke-through). Top = Z0 (PCB rests here).
    ld = PV["ledge_depth"]
    # rib outer reaches O_IN + push so it still merges with the pushed-out walls (the
    # board-rest inner edge is unchanged); without this the rib detaches -> 2 solids.
    ledge = frame_pad(body, "Pad_FC_Ledge", pcb_rest_z - ld, ld, O_IN + push, O_IN - PV["ledge_in"], SP("ledge_depth"))
    lth = ld   # downstream cuts (battery gap, drill notches) clear the full rib
    # 5a. Two notches in the +Y ledge rib (one per battery clip) so the clips' upper
    #     corner returns fit -- the battery is +Y-shifted, so those returns currently
    #     clip into this rib. Like the battery-connector gap: pocket the rib at each clip.
    yhi = PV["bat_ctr_y"] + PV["bat_body_y"]/2                # battery +Y edge
    for s in (-1, +1):
        rfc = PV["bat_ctr_x"] + s*PV["bat_body_x"]/2 + s*PV["clip_fit"]
        ce0 = min(rfc + s*PV["clip_wall"], rfc - s*PV["clip_return"]) - 0.6
        ce1 = max(rfc + s*PV["clip_wall"], rfc - s*PV["clip_return"]) + 0.6
        sub_box(body, "Cut_FC_ClipClr_%s" % ('L' if s < 0 else 'R'),
                ce0, yhi-0.6, pcb_rest_z-6.5, ce1-ce0, IY1-(yhi-0.6), 7.0)
    # carve the SCREEN space so the rib clears the REAL screen depth on the -X edge:
    # from the front floor up to just past the screen back (screen_back); the rib
    # remains above that (screen_back -> 0) to support the PCB.
    sx0, sx1, sy0, sy1 = -0.40, 71.60, 6.10, 36.10        # screen module footprint
    # carve scr_carve_in (1mm) into the inner -X wall for the screen edge/standoffs so
    # the board seats; the outer wall stays (2.4 - 1.0 = 1.4mm left -> no pop-through)
    clx0 = IX0 - PV["scr_carve_in"]
    sub_box(body, "Cut_FC_ScreenClear", clx0, sy0-0.3, front_floor_inner,
            (sx1+0.3)-clx0, (sy1-sy0)+0.6, (PV["screen_back"]+pcb_rest_z+PV["screen_cal"])-front_floor_inner)
    # 6. screen window (sized inside the screw holes)
    sub_box(body, "Cut_FC_Window", PV["win_x0"], PV["win_y0"], front_outer_z-1.0,
            PV["win_x1"]-PV["win_x0"], PV["win_y1"]-PV["win_y0"], W+2.0,
            L=f"{SP('win_x1')} - {SP('win_x0')}", Wd=f"{SP('win_y1')} - {SP('win_y0')}")
    # 6b. screen-clearance carve: shave 0.4mm off the BACK of the front face in the two
    #     frame strips at the screen's SHORTER (+/-X) edges, coming inward to the window,
    #     so the e-ink board edges sit clear of the inner face.
    scc = 0.40
    # each strip is pulled back 1mm from its window-facing edge (more solid frame by the window)
    sub_box(body, "Cut_FC_ScrFace_Xlo", sx0, sy0, front_floor_inner-scc,
            (PV["win_x0"]-1.0)-sx0, sy1-sy0, scc)
    scc_xhi = scc + 0.30   # +0.3mm deeper carve on the +X frame strip (screen edge fit)
    sub_box(body, "Cut_FC_ScrFace_Xhi", PV["win_x1"]+1.0, sy0, front_floor_inner-scc_xhi,
            sx1-(PV["win_x1"]+1.0), sy1-sy0, scc_xhi)
    # 7. round joystick boss (5 mm, annular fill around the hole)
    add_cyl(body, "Boss_FC_Joy", PV["joy_cx"], PV["joy_cy"], front_outer_z,
            PV["joy_boss_d"]/2, PV["joy_pad_th"])
    # (USB-C + switch live in the backplate now)
    # 10. battery-connector / cable gap (CN1, -Y): a blind pocket from the inside
    #     that reaches DOWN into the curved front-bottom for cable routing, but
    #     leaves `bat_floor` of solid front skin (a printable first layer). Starts
    #     at the wall inner so the outer wall stays solid.
    bat_z0 = front_outer_z + PV["bat_floor"]
    # Top reaches the PCB rest (rib top) so it cuts CLEAN THROUGH the ledge rib --
    # the rib pads up to pcb_rest_z (2.10), so stopping at 1.0 left a ~1.1mm shelf
    # over the connector/cable. Cutting to pcb_rest_z clears the full rib thickness.
    sub_box(body, "Cut_FC_BatteryGap",
            PV["bat_cx"]-PV["bat_gap_w"]/2, IY0, bat_z0,
            PV["bat_gap_w"], PV["bat_gap_d"], pcb_rest_z-bat_z0,
            L=SP("bat_gap_w"))
    # 10b. notch the rib around the 2 mount holes closest to the Y axis (x=2.4).
    #      z tracks the RAISED rib (pcb_rest_z - ld .. pcb_rest_z); cutting from the
    #      old -ld would slice through the front wall now that the rib sits higher.
    for i, (hx, hy) in enumerate(sorted(EINK_HOLES, key=lambda h: h[0])[:2]):
        sub_box(body, f"Cut_FC_DrillNotch{i}", IX0, hy-4.0, pcb_rest_z-ld-0.2,
                (hx+3.0)-IX0, 8.0, ld+0.7)
    # 11. lap tongue (rounded frame) with all-around clearance + snap bead
    fit = PV["lap_fit"]
    frame_pad(body, "Pad_FC_Tongue", seam_z, PV["lap"] - fit, O_TNG, O_IN + fit,
              f"{SP('lap')} - {SP('lap_fit')}")
    add_snap_beads(body)
    # Drop the snap bead on the straight +X (USB-C) short edge: it sat under the USB lip
    # and kept snapping off. Keep the corner beads; remove only the straight middle.
    sub_box(body, "Cut_FC_BeadGapUSB", BW+O_TNG, 8.0, bead_z-0.5,
            PV["bead_proj"]+1.0, (BH-8.0)-8.0, PV["bead_h"]+1.0)
    # 11e. Outer lip at the USB-C notch: fills the LOWER part of the backplate's USB
    #      cutout, flush with the outer +X surface (x = tongue outer .. OX1), rising
    #      from the seam by usb_lip_h to cover the exposed bead/seam. Sits inside the
    #      backplate notch with lap_fit clearance each side; the port mouth is above it.
    lip = add_box(body, "Lip_FC_USB",
                  BW + O_TNG, PV["usb_cy"] - (PV["usb_w"] - 2*PV["lap_fit"]) / 2, seam_z,
                  OX1 - (BW + O_TNG), PV["usb_w"] - 2*PV["lap_fit"], PV["usb_lip_h"])
    lip.setExpression("Length", f"{SP('wall')} - {SP('tongue_t')}")
    lip.setExpression("Width",  f"{SP('usb_w')} - 2 * {SP('lap_fit')}")
    lip.setExpression("Height", SP("usb_lip_h"))
    DOCO.recompute()
    # (no USB relief: the board rests ON the bead, so the USB-C base (~2.80) sits at/above
    #  the tongue top (2.8) and clears it -> the bead/tongue fully connect under the connector)
    # 12. joystick through-hole
    sub_cyl(body, "Cut_FC_Joy", PV["joy_cx"], PV["joy_cy"], front_outer_z-1.0,
            PV["joy_hole_d"]/2, PV["screen_top"]+PV["ftop"]+2.0)
    return body

# =====================================================================
# BACKPLATE  (deep cover: houses USB-C + Pico, curved closed back, clips on)
# =====================================================================
def build_backplate():
    body = DOCO.addObject("PartDesign::Body", "BackPlate")
    # 1. block seam(0) -> base_top
    sk = rect_sketch(body, "Sk_BP", seam_z, OX0, OY0, OX1, OY1)
    pad = body.newObject("PartDesign::Pad", "Pad_BP")
    pad.Profile = sk
    pad.Length = base_top_z - seam_z
    pad.setExpression("Length", SP("back_above"))
    DOCO.recompute()
    # 2. corner fillet  3. back-edge curve (same as the front)
    last = fillet(body, "Fillet_BP_Corners", pad, find_edges(pad, "vertical"),
                  PV["corner_r"], SP("corner_r"))
    te = find_edges(last, "top")
    if te:
        last = fillet(body, "Fillet_BP_Back", last, te, PV["back_curve"], SP("back_curve"))
    # 4. constant-wall curved shell, open at the seam (toward the front plate)
    last = shell_open_at(body, "Shell_BP", last, seam_z)
    # 5. lap relief (frame): receives the front-plate tongue
    frame_pocket(body, "Cut_BP_Relief", seam_z, PV["lap"], O_REL, O_IN, SP("lap"))
    # 6. snap recesses (capture the front-plate beads)
    add_snap_recesses(body)
    # 7. USB-C opening (+X). Start the cut inboard by back_curve so it also removes
    #    the top cap's inward lean (the rounded edge curves toward -X near the top);
    #    runs up through the cap (usb_z1 >= cap top) -> clean notch, no curve overhang.
    sub_box(body, "Cut_BP_USB", BW+C-PV["back_curve"]-1.0, PV["usb_cy"]-PV["usb_w"]/2, PV["usb_z0"],
            W+C+PV["back_curve"]+3.0, PV["usb_w"], PV["usb_z1"]-PV["usb_z0"],
            Wd=SP("usb_w"), H=f"{SP('usb_z1')} - {SP('usb_z0')}")
    # 8. power-switch pocket (-Y): BLIND, cut from the inside out to sw_skin short of the
    #    outer face, so the MSK12C02 actuator has room but no hole reaches the outside.
    pk_w = PV["sw_pocket_w"]; pk_y0 = -(C+W+EY) + PV["sw_skin"]
    sub_box(body, "Cut_BP_Switch", PV["sw_cx"]-pk_w/2, pk_y0, PV["sw_pocket_z0"]+pcb_rest_z,
            pk_w, -pk_y0 - C + 0.5, PV["sw_pocket_z1"]-PV["sw_pocket_z0"],
            L=SP("sw_pocket_w"), H=f"{SP('sw_pocket_z1')} - {SP('sw_pocket_z0')}")
    #    the actuator knob tip reaches y=-1.8 (0.1 into the 1mm skin): a shallow groove
    #    along its full travel (knob x 50.75..52.05 at one end, mirrored about sw_cx)
    #    leaves 0.75mm of skin there only. Knob z 4.36..5.06 (+0.15 clear).
    sub_box(body, "Cut_BP_SwitchKnob", PV["sw_cx"]-1.75, pk_y0-0.25, pcb_rest_z+2.10,
            3.5, 0.3, 1.0)
    # 9. perimeter SUPPORT SHELF: steps in over the board's outer edge from the board
    #    top up to the inner ceiling, so the board is clamped between the front rib
    #    (below) and this shelf (above). Open centre clears the Pico + accel/LEDs/caps.
    sh_h = (base_top_z - W) - board_top_z
    frame_pad(body, "Pad_BP_Shelf", board_top_z, sh_h, C, C - PV["back_shelf_reach"])
    # notch the shelf at the 4 M2 standoff holes (screws/standoffs pass through)
    for i, (hx, hy) in enumerate(EINK_HOLES):
        sub_cyl(body, f"Cut_BP_Standoff{i}", hx, hy, board_top_z-0.5, PV["standoff_clr"], sh_h+1.0)
    # gap only the INNER shelf for the edge parts (start at the wall inner, never cut
    # the side wall itself - the USB opening already pierces the wall).
    # USB-C (+X): remove the shelf band (wall inner -> reach inward)
    ux1 = BW + C + 0.1                                  # just inside the +X wall inner
    sub_box(body, "Cut_BP_ShelfUSB", ux1-(PV["back_shelf_reach"]+0.6), PV["usb_cy"]-PV["usb_w"]/2-0.6,
            board_top_z-0.5, PV["back_shelf_reach"]+0.6, PV["usb_w"]+1.2, sh_h+1.0)
    # Long-side edge gaps, made SYMMETRIC top/bottom: the -Y gap (powerswitch / TP4056 /
    # battery) and the +Y gap (MCU) share one X span and one depth in from each long wall,
    # so they're the same length and start/end at the same X on both sides.
    gx0, gx1 = 30.0, 56.0                              # common X span (covers switch+batt and MCU)
    gdep = 4.0                                         # reach in from the board edge (each side)
    sub_box(body, "Cut_BP_ShelfYedge", gx0, -(C+EY+0.1), board_top_z-0.5,
            gx1-gx0, (C+EY+0.1)+gdep, sh_h+1.0)        # -Y: wall inner -> y=+gdep
    sub_box(body, "Cut_BP_ShelfMCU",   gx0, BH-gdep,   board_top_z-0.5,
            gx1-gx0, (BH+C+EY+0.1)-(BH-gdep), sh_h+1.0)  # +Y: y=BH-gdep -> wall inner
    # +X corner LED gaps: keep the -Y corner one and MIRROR it onto the +Y corner.
    lc_x, lc_w, lc_dep = 85.0, 8.0, 4.0
    sub_box(body, "Cut_BP_ShelfLED",    lc_x, -(C+EY+0.1), board_top_z-0.5,
            lc_w, (C+EY+0.1)+lc_dep, sh_h+1.0)         # +X/-Y corner
    sub_box(body, "Cut_BP_ShelfLEDtop", lc_x, BH-lc_dep, board_top_z-0.5,
            lc_w, (BH+C+EY+0.1)-(BH-lc_dep), sh_h+1.0) # +X/+Y corner (mirror)
    # thin the central back panel 0.2mm (translucent filament -> see the components more
    # clearly). Inset from the walls past the support shelf so the perimeter/shelf stay
    # full thickness; shaves only the flat inner base over the board.
    inset = PV["back_shelf_reach"] + 0.5
    sub_box(body, "Cut_BP_BaseThin", IX0+inset, IY0+inset, base_top_z-W,
            (IX1-inset)-(IX0+inset), (IY1-inset)-(IY0+inset), 0.2)
    # skim the OUTER back face down by back_skim over the whole footprint (the cap's
    # flat top drops; the inner ceiling/shelf stay put, so only the panel thins)
    sk_ = PV["back_skim"]
    sub_box(body, "Cut_BP_BackSkim", OX0-1.0, OY0-1.0, base_top_z-sk_,
            (OX1-OX0)+2.0, (OY1-OY0)+2.0, sk_+1.0)
    return body

# =====================================================================
# THUMBPIECE
# =====================================================================
def build_thumbpiece():
    body = DOCO.addObject("PartDesign::Body", "Thumbpiece")
    cx, cy = PV["joy_cx"], PV["joy_cy"]
    bot = front_outer_z + 0.10
    disc = add_cyl(body, "Thumb_Disc", cx, cy, bot, PV["thumb_od"]/2, PV["thumb_h"])
    disc.setExpression("Radius", f"{SP('thumb_od')} / 2")
    disc.setExpression("Height", SP("thumb_h"))
    DOCO.recompute()
    sph = body.newObject("PartDesign::SubtractiveSphere", "Thumb_Dish")
    sph.Radius = PV["thumb_dish_r"]
    sph.Placement = App.Placement(V(cx, cy, bot - PV["thumb_dish_r"] + PV["thumb_dish_d"]), ROT0)
    sph.setExpression("Radius", SP("thumb_dish_r"))
    DOCO.recompute()
    s = PV["thumb_sock"]
    top = bot + PV["thumb_h"]
    sub_box(body, "Thumb_Socket", cx-s/2, cy-s/2, top-PV["thumb_sock_d"], s, s, PV["thumb_sock_d"]+0.1)
    return body

# =====================================================================
# BATTERY END-CLIPS  (two printed corner pieces that hook the standoff pillars and
#                     wall the battery's corners, wedged in the PCB->screen gap)
# =====================================================================
def build_battery_clip(sx, name):
    """ONE end-clip for the -X (sx=-1) or +X (sx=+1) end of the battery. It hooks the
       two M2 standoff pillars at that end (notch/hole that the pillar pokes into) and
       walls the battery's two corners there. Height spans the full PCB-screen-side-face
       -> screen-back gap, so it wedges between them AND covers the 5mm cell. The cell is
       sandwiched in X between the two clips' rails and held in Y by the corner returns;
       the pillars locate each clip. Avoids the -Y connector entirely (clips are at the
       X-ends). Standalone print (not booleaned into the case)."""
    body = DOCO.addObject("PartDesign::Body", name)
    bx, by = PV["bat_body_x"], PV["bat_body_y"]
    cx, cy = PV["bat_ctr_x"], PV["bat_ctr_y"]
    fit, cw = PV["clip_fit"], PV["clip_wall"]
    pr, rl  = PV["clip_pillar_r"], PV["clip_return"]
    # Z: the rail/returns cover the battery (+ a little), leaving a gap below their middle
    # so they don't crush screen-back components. The standoff BOSSES instead run the FULL
    # standoff height (10mm) -- PCB screen-side face down to the screen back -- so they meet
    # the e-ink PCB and clamp the screen + the clip in place.
    z1 = pcb_rest_z                                          # PCB screen-side face (top)
    z0 = z1 - PV["bat_body_z"]                               # rail/returns cover the cell
    h  = z1 - z0
    boss_z0 = pcb_rest_z - PV["standoff_h"] + 0.2            # 0.2 short of the screen back: clearance at the tallest point
    boss_h  = pcb_rest_z - boss_z0                           # ~9.8mm (just under the 10mm standoff)
    bx_edge = cx + sx*bx/2                                   # battery end edge X
    by_lo, by_hi = cy - by/2, cy + by/2                      # battery corners (Y)
    rail_face = bx_edge + sx*fit                             # clears the battery edge
    rail_out  = rail_face + sx*cw
    rx0, rx1  = min(rail_face, rail_out), max(rail_face, rail_out)
    # 1. battery-edge rail (X-stop). Y span runs the corner-outboard band (past both
    #    corners by a wall) so the returns and pillar tabs share a real face with it
    #    and the whole clip fuses into ONE solid.
    ry0, ry1 = by_lo - fit - cw, by_hi + fit + cw
    add_box(body, "Clip_Rail", rx0, ry0, z0, rx1-rx0, ry1-ry0, h)
    # 2. corner returns (Y-stops) reaching inward along the battery edge at each corner;
    #    start at the rail's outboard face so they overlap the rail body.
    ret_x0 = min(rail_out, rail_face - sx*rl)
    ret_x1 = max(rail_out, rail_face - sx*rl)
    add_box(body, "Clip_RetLo", ret_x0, by_lo-fit-cw, z0, ret_x1-ret_x0, cw, h)
    add_box(body, "Clip_RetHi", ret_x0, by_hi+fit,    z0, ret_x1-ret_x0, cw, h)
    # 2b. Z-retention overhang: a clip_lip_th-thick flange under each corner return
    #     (screen side), reaching clip_lip_proj inward OVER the battery's corner so the
    #     cell rests on it. The PCB face caps the top -> cell trapped in Z. Spans back
    #     into the return so it shares a face and stays one solid.
    lpj, lth = PV["clip_lip_proj"], PV["clip_lip_th"]
    add_box(body, "Clip_LipLo", ret_x0, by_lo-fit-cw, z0-lth,
            ret_x1-ret_x0, cw + lpj, lth)                      # lower corner: reach +Y over the cell
    add_box(body, "Clip_LipHi", ret_x0, by_hi+fit-lpj, z0-lth,
            ret_x1-ret_x0, cw + lpj, lth)                      # upper corner: reach -Y over the cell
    # 3. pillar tabs at the two standoffs on this end, each notched/holed to cup a pillar.
    #    Reach outward toward the pillar but never cross the case wall: where the wall is
    #    close (-X end) the clamp turns the hole into an OPEN notch; where there's room
    #    (+X end) it stays a closed hole that fully locates the clip.
    so_x = min(p[0] for p in EINK_HOLES) if sx < 0 else max(p[0] for p in EINK_HOLES)
    wall_in = IX0 if sx < 0 else IX1
    half = pr + fit + cw                                     # tab half-width past the pillar
    for sy in sorted({p[1] for p in EINK_HOLES}):
        tab_out = so_x + sx*half
        tab_out = max(tab_out, wall_in + 0.3) if sx < 0 else min(tab_out, wall_in - 0.3)
        tx0, tx1 = min(rail_face, tab_out), max(rail_face, tab_out)
        add_box(body, f"Clip_Tab{int(round(sy))}", tx0, sy-half, boss_z0, tx1-tx0, 2*half, boss_h)
        sub_cyl(body, f"Clip_Notch{int(round(sy))}", so_x, sy, boss_z0-0.5, pr+fit, boss_h+1.0)
        # Open the post hole into a SLOT so no thin boss wall is left. The +X clip opens
        # toward the header/origin (inboard); the -X clip opens toward the case wall
        # (outboard, where a closed boss would be ~0.2mm and unprintable). The rail-side
        # half of the cup stays, tied to the rail, so it still locates the clip.
        if sx > 0:
            ox0, oxw = rail_face-0.5, so_x-(rail_face-0.5)          # open inboard (toward header)
        else:
            ox0, oxw = so_x-half-0.5, half+0.5                      # open outboard (toward -X wall)
        sub_box(body, f"Clip_Open{int(round(sy))}", ox0, sy-(pr+fit), boss_z0-0.5,
                oxw, 2*(pr+fit), boss_h+1.0)
    # +X end: notch the header-side of the rail so it clears the e-ink header (x67-70,
    # y17-25). Only the outboard sliver of the rail is removed (keeps an inner spine so
    # the clip stays one piece); does nothing on the -X clip.
    if sx > 0:
        hx0, hx1 = 67.0, 72.0
        hy0, hy1 = 16.0, 26.0
        if hx1 > rail_face:
            sub_box(body, "Clip_HdrNotch", max(hx0, rail_face+0.8), hy0, boss_z0-0.5,
                    hx1-max(hx0, rail_face+0.8), hy1-hy0, boss_h+1.0)
    # -X clip: shave 2.5mm off the short-edge (-X) side so it clears the front-case short
    # wall (the post slot is open that way, so the +X cup that grips the post is untouched).
    if sx < 0:
        sh, xe = 2.5, wall_in + 0.3                          # xe = the clip's -X edge
        sub_box(body, "Clip_Shave", xe-1.0, ry0-1.0, boss_z0-0.5,
                (xe+sh)-(xe-1.0), (ry1-ry0)+2.0, boss_h+1.0)
    return body

# =====================================================================
# IMPORT ASSEMBLY (reference)
# =====================================================================
def import_assembly():
    path = "/home/rompasaurus/COdingProjects/Dilder-PCB/Case Design/Dilder_PCB_FullAssembly.step"
    if not os.path.exists(path):
        return None
    raw = Part.Shape(); raw.read(path)
    # XY into the local frame; +Z raises the whole board to its rest height (board_rest_z)
    raw.translate(V(-46.70, 88.00, PV["board_rest_z"]))
    # Calibration: keep the screen at its AUTHORITATIVE STEP position (reality).
    # The screen's real front face is at z=-8.64; the case window-frame inner face is
    # at front_outer_z+wall=-10.0, so the real screen sits ~1.36mm behind the frame
    # (a genuine air gap, not a clip). screen_cal nudges it if needed (+ = toward
    # the board). The old build shoved it -1.36mm onto the front floor, which made it
    # clip the frame in the model; screen_cal=0 restores reality.
    dz = PV["screen_cal"]
    rz = PV["board_rest_z"]            # thresholds move up with the raised board
    kept = []
    for s in raw.Solids:
        b = s.BoundBox
        if b.ZMax > 6.0 + rz:          # strip only the tall header pins (orig ZMax~10), not the raised Pico/USB
            continue
        cx, cy = (b.XMin+b.XMax)/2, (b.YMin+b.YMax)/2
        if b.ZMax < -5.0 + rz and -2 < cx < 73 and 4 < cy < 38:
            t = s.copy(); t.translate(V(0, 0, dz)); kept.append(t)
        else:
            kept.append(s)
    obj = DOCO.addObject("Part::Feature", "Dilder_Assembly")
    obj.Shape = Part.makeCompound(kept)
    if GUI and obj.ViewObject:
        obj.ViewObject.ShapeColor = (0.55, 0.55, 0.58)
    return obj

# =====================================================================
# RUN
# =====================================================================
bp = build_backplate()
fc = build_front_cover()
tp = build_thumbpiece()
clipL = build_battery_clip(-1, "BatteryClipL")
clipR = build_battery_clip(+1, "BatteryClipR")
asm = import_assembly()
DOCO.recompute()

# Clips are built in place (no spin): left build sits on the left posts with closed
# bosses + rail on the left battery edge; right build sits on the right posts with the
# origin-side of its bosses opened + rail on the right battery edge (by the header).

# 10mm M2 brass standoffs at the 4 e-ink mount holes: from the PCB screen-side face
# (pcb_rest_z) toward the screen (-Z) by standoff_h. Assembly reference (not printed).
_so = [Part.makeCylinder(PV["standoff_d"]/2, PV["standoff_h"],
                         V(hx, hy, pcb_rest_z), V(0, 0, -1)) for (hx, hy) in EINK_HOLES]
standoffs = DOCO.addObject("Part::Feature", "Standoffs")
standoffs.Shape = Part.makeCompound(_so)
if GUI and standoffs.ViewObject:
    standoffs.ViewObject.ShapeColor = (0.80, 0.62, 0.28)   # brass
DOCO.recompute()

if GUI:
    for b, col in [(bp,(0.30,0.55,0.85)), (fc,(0.85,0.55,0.30)), (tp,(0.15,0.15,0.18)),
                   (clipL,(0.85,0.20,0.30)), (clipR,(0.85,0.20,0.30))]:
        try: b.ViewObject.ShapeColor = col
        except Exception: pass

here = os.path.dirname(os.path.abspath(__file__)) if "__file__" in globals() else os.getcwd()
proj = os.path.dirname(here) if os.path.basename(here) == "freecad" else here
DOCO.saveAs(os.path.join(here, "WetGregCase.FCStd"))
exp = os.path.join(proj, "exports")
try:
    os.makedirs(exp, exist_ok=True)
    Part.export([bp], os.path.join(exp, "WetGregCase_BackPlate.step"))
    Part.export([fc], os.path.join(exp, "WetGregCase_FrontCover.step"))
    Part.export([tp], os.path.join(exp, "WetGregCase_Thumbpiece.step"))
    Part.export([clipL], os.path.join(exp, "WetGregCase_BatteryClipL.step"))
    Part.export([clipR], os.path.join(exp, "WetGregCase_BatteryClipR.step"))
except Exception as e:
    App.Console.PrintWarning("STEP export skipped: %s\n" % e)
try:                                   # print-ready 3MF meshes (regenerated each run)
    import Mesh
    for o, nm in [(fc, "FrontCover"), (bp, "BackPlate"), (tp, "Thumbpiece"),
                  (clipL, "BatteryClipL"), (clipR, "BatteryClipR")]:
        Mesh.export([o], os.path.join(here, "WetGregCase-%s.3mf" % nm))
except Exception as e:
    App.Console.PrintWarning("3MF export skipped: %s\n" % e)

def chk(b):
    s = b.Shape
    return f"solids={len(s.Solids)} valid={s.isValid()} closed={s.isClosed()}"
print("="*62)
print("WetGregCase (PartDesign + Parameters spreadsheet)")
print("  BackPlate :", chk(bp))
print("  FrontCover:", chk(fc))
print("  Thumbpiece:", chk(tp))
print("  BatClip L :", chk(clipL))
print("  BatClip R :", chk(clipR))
print("  Overall Z : %.2f .. %.2f (%.2f mm)" % (front_outer_z, base_top_z-PV["back_skim"], base_top_z-PV["back_skim"]-front_outer_z))
print("  Case Y    : %.2f .. %.2f (%.2f mm, +%.1f total)" % (OY0, OY1, OY1-OY0, 2*EY))
print("="*62)

if GUI:
    try:
        import FreeCADGui as Gui
        Gui.activeDocument().activeView().viewIsometric()
        Gui.SendMsgToActiveView("ViewFit")
    except Exception:
        pass
